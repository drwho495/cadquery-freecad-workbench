# -*- coding: utf-8 -*-
# Macro to demonstrate creating and using a CodeFeature object via MacroPath

import FreeCAD
import FreeCADGui
import os # For path joining

try:
    # Assuming CQGui is in a place FreeCAD can find (e.g., Mod/cadquery-freecad-workbench/CQGui)
    from CQGui.CodeFeature import createCodeFeature, executeCodeFeature
except ImportError as e:
    FreeCAD.Console.PrintError("Error importing from CQGui.CodeFeature: {}\n".format(e))
    FreeCAD.Console.PrintError("Please ensure the CadQuery workbench is correctly installed and its modules are in sys.path.\n")
    raise # Re-raise the exception if the import fails, to stop the macro.

def runMacro():
    """Main function to run the macro's operations."""
    
    doc = FreeCAD.activeDocument()
    if not doc:
        doc = FreeCAD.newDocument("CodeFeatureMacroDemo")
        FreeCAD.Console.PrintMessage("Created new document: CodeFeatureMacroDemo\n")
    else:
        FreeCAD.Console.PrintMessage("Using active document: {}\n".format(doc.Name))

    try:
        thisMacroPath = __file__
        macrosDir = os.path.dirname(thisMacroPath)
    except NameError: 
        macrosDir = FreeCAD.getUserMacroDirMap().get("User macros", ".")
        FreeCAD.Console.PrintWarning("__file__ not defined, assuming macrosDir: {}\n".format(macrosDir))

    cqSphereMacroFile = os.path.join(macrosDir, "CQ_Sphere_For_CodeFeature.FCMacro")
    b3dBoxMacroFile = os.path.join(macrosDir, "B3D_Box_For_CodeFeature.FCMacro")

    if not os.path.exists(cqSphereMacroFile):
        FreeCAD.Console.PrintError(f"Example macro CQ_Sphere_For_CodeFeature.FCMacro not found at {cqSphereMacroFile}\n")
        return
    if not os.path.exists(b3dBoxMacroFile):
        FreeCAD.Console.PrintError(f"Example macro B3D_Box_For_CodeFeature.FCMacro not found at {b3dBoxMacroFile}\n")
        return

    FreeCAD.Console.PrintMessage("Creating a new Code Feature...\n")
    cfObject = createCodeFeature(doc, name="MyMacroDrivenFeature")

    if not cfObject:
        FreeCAD.Console.PrintError("Failed to create Code Feature.\n")
        return
    FreeCAD.Console.PrintMessage(f"Code Feature '{cfObject.Label}' created.\n")

    FreeCAD.Console.PrintMessage("Configuring for a CadQuery sphere via macro...\n")
    cfObject.MacroPath = cqSphereMacroFile
    cfObject.GeneratedObjectLabel = "Sphere via Macro (CQ)" 
    executeCodeFeature(cfObject)
    if FreeCAD.ActiveDocument: FreeCAD.ActiveDocument.recompute()
    FreeCAD.Console.PrintMessage("Sphere via macro should now be visible.\n")

    FreeCAD.Console.PrintMessage(f"\nReconfiguring '{cfObject.Label}' for a Build123D box via macro...\n")
    cfObject.MacroPath = b3dBoxMacroFile
    cfObject.GeneratedObjectLabel = "Box via Macro (b3d)"
    executeCodeFeature(cfObject)
    if FreeCAD.ActiveDocument: FreeCAD.ActiveDocument.recompute()
    FreeCAD.Console.PrintMessage("Object should now be a box.\n")

    FreeCAD.Console.PrintMessage("\nMacro finished.\n")

if __name__ == "__main__":
    try:
        runMacro()
    except Exception as e:
        import traceback
        FreeCAD.Console.PrintError("Macro execution failed: \n{}".format(traceback.format_exc()))
